package PotatoDrive {
    package Bindings {
        package GPhotos {}
        package Proxy {}
        package S3 {}
        package SFTP {}
        package Utils {}
    }
    package Cmd {
        package Config {}
        package Main {}
        package Mgr {}
        package OAuth {}
        package Proxy {}
        package RegAddPerm {}
    }
    package Core {
        package CFAPI {
            package Filesystem {}
        }
        package CFG {}
        package ProjFS {
            package Filesystem {}
        }
        package Tasks {}
    }
    package Docs {}
    package Example {}
    package GPFS {}
    package Test {
        package Minio {}
    }
    package UI {}
    package WinRTGo {
        package Cmd {
            package WinRTGoGen {}
        }
        package Internal {
            package CLI {}
            package Codegen {}
            package WinMD {}
        }
    }
}
